KSUDO DEFINITIONS ::=
BEGIN

-- Heimdal's ASN.1 compiler can only cope with limits that exactly match
-- unsigned? int. Grr.
ksudo_int32 ::= INTEGER (-2147483648..2147483647)
ksudo_uint32 ::= INTEGER (0..4294967295)

KSUDO-ERR-CODE ::= INTEGER {
    KSUDO_OK(0),
    KSUDO_ENOENT(1),
    KSUDO_EACCES(2),
    KSUDO_ENOEXEC(3),
    KSUDO_EPERM(4),
    KSUDO_WINDOW_EXCEEDED(5)
}

KSUDO-ERR ::= SEQUENCE {
    code        KSUDO-ERR-CODE,
    msg         IA5String
}

KSUDO-ENVOPT-CWD ::= OCTET STRING

KSUDO-ENVOPT-ENV ::= SEQUENCE {
    name        OCTET STRING,
    value       OCTET STRING
}

KSUDO-FD-MODE ::= INTEGER {
    KSUDO_FD_READ(0),
    KSUDO_FD_WRITE(1),
    KSUDO_FD_RDWR(2)
}

-- see above
--KSUDO-FDNUM ::= INTEGER (-1..9)
KSUDO-FDNUM ::= ksudo_int32

KSUDO-ENVOPT-REMOTEFD ::= SEQUENCE {
    fd      KSUDO-FDNUM,
    mode    KSUDO-FD-MODE
}

KSUDO-ENVOPT-LOCALFD ::= SEQUENCE {
    fd      KSUDO-FDNUM,
    mode    KSUDO-FD-MODE,
    path    OCTET STRING
}

KSUDO-ENVOPT-DUPFD ::= SEQUENCE {
    fd      KSUDO-FDNUM,
    onto    KSUDO-FDNUM
}

KSUDO-ENVOPT-TTY ::= NULL

KSUDO-ENV-OPT ::= CHOICE {
    cwd     [0] KSUDO-ENVOPT-CWD,
    rfd     [1] KSUDO-ENVOPT-REMOTEFD,
    lfd     [2] KSUDO-ENVOPT-LOCALFD,
    dup     [3] KSUDO-ENVOPT-DUPFD,
    tty     [4] KSUDO-ENVOPT-TTY
}

KSUDO-CMD ::= SEQUENCE {
    user        IA5String,
    cmd         SEQUENCE OF OCTET STRING,
    env         SEQUENCE OF KSUDO-ENV-OPT
}

KSUDO-DATA ::= SEQUENCE {
    fd      KSUDO-FDNUM,
    data    OCTET STRING
}

KSUDO-WNDSIZE ::= ksudo_uint32

KSUDO-WINDOW ::= SEQUENCE {
    fd      KSUDO-FDNUM,
    incr    KSUDO-WNDSIZE
}

KSUDO-CLOSE ::= KSUDO-FDNUM

-- list taken from SUSv4
KSUDO-SIGNAL ::= INTEGER {
    KSUDO_SIGABRT(1),
    KSUDO_SIGALRM(2),
    KSUDO_SIGBUS(3),
    -- CHLD
    -- CONT
    KSUDO_SIGFPE(6),
    KSUDO_SIGHUP(7),
    KSUDO_SIGILL(8),
    KSUDO_SIGINT(9),
    KSUDO_SIGKILL(10),
    KSUDO_SIGPIPE(11),
    KSUDO_SIGQUIT(12),
    KSUDO_SIGSEGV(13),
    -- STOP
    KSUDO_SIGTERM(15),
    -- TSTP
    -- TTIN
    -- TTOU
    KSUDO_SIGUSR1(19),
    KSUDO_SIGUSR2(20),
    KSUDO_SIGTRAP(21),
    -- URG
    KSUDO_SIGXCPU(23),
    KSUDO_SIGXFSZ(24),
    KSUDO_SIGSYS(25)
}

-- see above
--KSUDO-STATUS ::= INTEGER (0..255)
KSUDO-STATUS ::= ksudo_int32

KSUDO-EXIT ::= CHOICE {
    status  [0] KSUDO-STATUS,
    signal  [1] KSUDO-SIGNAL,
    unknown [2] NULL
}

KSUDO-MSG ::= CHOICE {
    err     [0] KSUDO-ERR,
    cmd     [1] KSUDO-CMD,
    data    [2] KSUDO-DATA,
    window  [3] KSUDO-WINDOW,
    close   [4] KSUDO-CLOSE,
    signal  [5] KSUDO-SIGNAL,
    exit    [6] KSUDO-EXIT
}

END
